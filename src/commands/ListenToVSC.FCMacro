import threading
import socket
import FreeCAD as App

def start_vsc_listener():
    # Socket erstellen
    s = socket.socket(socket.AF_INET, socket.SOCK_STREAM)
    s.setsockopt(socket.SOL_SOCKET, socket.SO_REUSEADDR, 1)
    try:
        s.bind(('localhost', 9999))
        s.listen(1)
        App.Console.PrintMessage("VSC-Server: Höre auf Port 9999...\n")
        
        while True:
            conn, addr = s.accept()
            try:
                data = conn.recv(1024 * 20).decode('utf-8')
                if data:
                    # Der Code von VSC wird hier ausgeführt
                    exec(data, globals())
            except Exception as e:
                App.Console.PrintError(f"VSC-Server Fehler beim Ausführen: {str(e)}\n")
            finally:
                conn.close()
    except Exception as e:
        App.Console.PrintError(f"VSC-Server konnte nicht starten: {str(e)}\n")
    finally:
        s.close()

# Server in einem eigenen Thread starten, damit FreeCAD nicht einfriert
thread = threading.Thread(target=start_vsc_listener, daemon=True)
thread.start()
