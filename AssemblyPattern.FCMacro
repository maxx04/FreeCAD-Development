import FreeCAD as App
import FreeCADGui as Gui

def convert_array_to_smart_group():
    doc = App.ActiveDocument
    selection = Gui.Selection.getSelection()
    
    if len(selection) != 1:
        App.Console.PrintError("Bitte das Draft-Array auswählen.\n")
        return

    array_obj = selection[0]
    base_obj = array_obj.Base
    
    # 1. Parent Assembly finden
    parent_asm = None
    for p in base_obj.InList:
        if p.isDerivedFrom("App::Part"):
            parent_asm = p
            break
            
    if not parent_asm:
        App.Console.PrintError("Keine Assembly gefunden.\n")
        return

    # 2. Gruppe erstellen
    group_name = f"Muster_{base_obj.Label}"
    pattern_group = doc.getObject(group_name)
    if not pattern_group:
        pattern_group = doc.addObject("App::DocumentObjectGroup", group_name)
        pattern_group.Label = f"Muster {base_obj.Label}"
        parent_asm.addObject(pattern_group)

    # 3. Positionen holen (Expand erzwingen)
    array_obj.ExpandArray = True
    doc.recompute()
    
    # Wir nehmen die echten Unter-Objekte (Array_i0, i1...)
    sub_elements = [o for o in array_obj.OutList if "Array_i" in o.Name]

    # 4. DAS ORIGINALTEIL INTEGRIEREN
    # Wir verschieben das Original in die Gruppe. Es wird unser "Teil 0".
    if base_obj not in pattern_group.Group:
        pattern_group.addObject(base_obj)
    base_obj.Visibility = True # Sicherstellen, dass man es sieht

    # 5. LINKS ERSTELLEN (AB INDEX 1)
    doc.openTransaction("Smart Grouping")
    
    # Alte Links dieser Serie löschen
    link_prefix = f"Lnk_{base_obj.Name}_"
    for obj in doc.Objects:
        if obj.Name.startswith(link_prefix):
            doc.removeObject(obj.Name)

    # Matrizen für die Korrektur
    m_asm_inv = parent_asm.getGlobalPlacement().inverse().toMatrix()
    m_array_world = array_obj.getGlobalPlacement().toMatrix()

    # Wir starten die Schleife erst ab dem zweiten Element (Index 1)
    for i in range(1, len(sub_elements)):
        el = sub_elements[i]
        link_name = f"{link_prefix}{i:02d}"
        
        new_link = doc.addObject("App::Link", link_name)
        new_link.setLink(base_obj)
        new_link.Label = base_obj.Label
        
        # Position berechnen
        m_copy_world = m_array_world.multiply(el.Placement.toMatrix())
        new_link.Placement = App.Placement(m_asm_inv.multiply(m_copy_world))
        
        pattern_group.addObject(new_link)

    # Array stumm schalten
    array_obj.Visibility = False
    
    doc.commitTransaction()
    doc.recompute()
    App.Console.PrintMessage(f"ERFOLG: Original + {len(sub_elements)-1} Links in Gruppe vereint.\n")

convert_array_to_smart_group()
